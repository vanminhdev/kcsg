module sina {
    yang-version 1.1;
    namespace "urn:opendaylight:params:xml:ns:yang:sina";
    prefix "sina";

    revision "2020-09-08" { // TODO change revision to date of model creation
        description "Initial revision of sina model";
    }

    rpc compareVersions {
        input {
            leaf data {
                type string;
            }
        }
        output {
            leaf ips {
                type string;
            }
        }
    }

    rpc updateNewData {
        input {
            leaf data {
                type string;
            }
        }
        output {
            leaf result {
                type string;
            }
        }
    }
}
